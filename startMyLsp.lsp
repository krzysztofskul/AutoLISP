(defun c:startMyLsp()

	(load "D:/KSKLN/IT/AutoLISP/myCommands.lsp")
	(load "D:/KSKLN/IT/AutoLISP/myLispApps-route-sketcher.lsp")
	(load "D:/KSKLN/IT/AutoLISP/myLispApps-myrectangle.lsp")
	(load "D:/KSKLN/IT/AutoLISP/myLispApps.lsp")

	(load "D:/KSKLN/IT/AutoLISP/setLayers.lsp")
	(load "D:/KSKLN/IT/AutoLISP/changeLayerFunctions.lsp")
	(load "D:/KSKLN/IT/AutoLISP/updateExistingLayers.lsp")
	(load "D:/KSKLN/IT/AutoLISP/layerTransparency.lsp")

	(load "D:/KSKLN/IT/AutoLISP/ductAll.lsp")
	(load "D:/KSKLN/IT/AutoLISP/ductOpening.lsp")
	(load "D:/KSKLN/IT/AutoLISP/ductRoute.lsp")
	(load "D:/KSKLN/IT/AutoLISP/getRoute.lsp")
	(load "D:/KSKLN/IT/AutoLISP/myWallSketcher.lsp")
	(load "D:/KSKLN/IT/AutoLISP/myRectangle.lsp")
	(load "D:/KSKLN/IT/AutoLISP/myRectangleOnEllipse.lsp")
	(load "D:/KSKLN/IT/AutoLISP/blockOperations.lsp")	
	(load "D:/KSKLN/IT/AutoLISP/test.lsp")
	
	(c:toGrayHSCAD)
	
)
